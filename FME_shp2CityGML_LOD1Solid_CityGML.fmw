FME workspace FME_shp2CityGML_LOD1Solid_CityGML.fmw

Parameters:
- DestDataset_CITYGML_5 = 3d_iitb_utm43   # Destination CityGML Document
- SourceDataset_SHAPEFILE = C:\Assignments\MTechGeo\DRP\iitb_utm43.shp   # Source Esri Shapefile(s)
- DestDataset_CITYGML_4 = C:\Assignments\MTechGeo\DRP\Data\gmliitb.gml   # Destination CityGML Document

Readers:
- SHAPEFILE_1: SHAPEFILE from $(SourceDataset_SHAPEFILE)

Writers:
- CITYGML_2: CITYGML to $(DestDataset_CITYGML_5)
- CITYGML_3: CITYGML to $(DestDataset_CITYGML_4)

iitb_utm43 (reader SHAPEFILE_1)
    attributes: OBJECTID number(19,0), Shape_Area double, Shape_Leng double, ID varchar(5), PLOT varchar(1), NAME varchar(40), NUMBER varchar(5), TYPE varchar(11), FLOORS varchar(3), FLOOR_TYPE varchar(15), HEIGHT long, AREA varchar(8), STATUS varchar(18), DEPT1 varchar(30), DEPT2 varchar(254), UNIT_NO_ varchar(20), Z_OF_UNITS varchar(4), YR_OF_CONS varchar(10), CRPT_AREA varchar(7), BU_AREA varchar(7), YR_OF_DEMO varchar(4), YR_OF_CO_1 varchar(10), area_1 float
    -> Extruder
Extruder
    DIRECTION = Auto
    DISTANCE = @Value(HEIGHT)
    EXTRUDED -> AttributeCreator
AttributeCreator
    ATTR_TABLE = SET_TO citygml_lod_name (buffer) = lod1Solid
    -> GeometryPropertySetter
GeometryPropertySetter
    OVERWRITE_CHOICE = Yes
    REMOVE_ATTRIBUTE = No
    SETTYPE_PARAM = Traits From Attributes
    SRC_ATTRS = citygml_lod_name
    SET -> Building (writer CITYGML_3)
Building (writer CITYGML_3)
    attributes: citygml_feature_role xml_buffer, gml_name xml_buffer, citygml_year_of_construction xml_buffer, citygml_measured_height xml_real64, citygml_storeys_above_ground xml_uint64, citygml_level_of_detail00 xml_buffer
Building (writer CITYGML_2)
    attributes: citygml_feature_role xml_buffer, gml_name xml_buffer, citygml_year_of_construction xml_buffer, citygml_measured_height xml_real64, citygml_storeys_above_ground xml_uint64, citygml_level_of_detail_ xml_buffer
